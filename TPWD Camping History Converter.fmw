FME workspace TPWD Camping History Converter.fmw

Creator
    GEOMTYPE = Geometry Object
    NUM = 1
    CREATED -> FeatureReader [INITIATOR]
    CREATED -> FeatureReader_2 [INITIATOR]
    CREATED -> FeatureReader_3 [INITIATOR]
Note: read camping history from AGO
FeatureReader_3
    ARCGISONLINEFEATURES_CREATE_FEATURE_TABLES_FROM_DATA = Yes
    ARCGISONLINEFEATURES_FEATURESERVICE = mikedoesgis/Camping/camping_history(08c11fdd9f074462a1d36fbff490906e)
    ARCGISONLINEFEATURES_FEATURES_PER_REQUEST = 1000
    ARCGISONLINEFEATURES_FORMAT_GUID = YES
    ARCGISONLINEFEATURES_NC = Mike Does GIS
    ARCGISONLINEFEATURES_QUERY_FEATURE_TYPES_FOR_MERGE_FILTERS = Yes
    ARCGISONLINEFEATURES_RESOLVE_DOMAINS = No
    ARCGISONLINEFEATURES_USE_SEARCH_ENVELOPE = NO
    ATTRIBUTES = Camp_Sites,"campground,camp_site,fromdate,todate,reservation_number,reservation_details,total_fee,OBJECTID,Longitude,Latitude,days,phone,tmobile_data,att_data,shade,levelness,privacy,water,GlobalID"
    ATTR_ACCUM_MODE = Only Use Result
    COMBINE_GEOM = Use Result
    FEATURETYPES = Camp_Sites
    FORMAT = ARCGISONLINEFEATURES
    INTERACT = NONE
    ORDER_RESULTS = No
    OUTPUT_FEATURES_DISPLAY = Schema and Data Features
    Camp_Sites -> ChangeDetector [ORIGINAL]
    Camp_Sites -> AttributeManager_5
AttributeManager_5
    ATTR_TABLE:
      REMOVE campground (varchar(100))
      REMOVE camp_site (varchar(20))
      REMOVE fromdate (datetime)
      REMOVE todate (datetime)
      REMOVE reservation_details (varchar(200))
      REMOVE total_fee (real64)
      REMOVE Longitude (real64)
      REMOVE Latitude (real64)
      REMOVE days (int32)
      REMOVE phone (varchar(5))
      REMOVE tmobile_data (varchar(5))
      REMOVE att_data (varchar(5))
      REMOVE shade (varchar(10))
      REMOVE levelness (varchar(20))
      REMOVE privacy (varchar(20))
      REMOVE water (varchar(50))
      REMOVE GlobalID (varchar(38))
    -> FeatureMerger_2 [SUPPLIER]
Note: read camping boundaries from AGO
FeatureReader_2
    ARCGISONLINEFEATURES_CREATE_FEATURE_TABLES_FROM_DATA = Yes
    ARCGISONLINEFEATURES_FEATURESERVICE = mikedoesgis/Camping/camping(82b057feca404205b2b993f5e6aa7b40)
    ARCGISONLINEFEATURES_FEATURES_PER_REQUEST = 1000
    ARCGISONLINEFEATURES_FORMAT_GUID = YES
    ARCGISONLINEFEATURES_NC = Mike Does GIS
    ARCGISONLINEFEATURES_QUERY_FEATURE_TYPES_FOR_MERGE_FILTERS = Yes
    ARCGISONLINEFEATURES_RESOLVE_DOMAINS = Yes
    ARCGISONLINEFEATURES_USE_SEARCH_ENVELOPE = NO
    ATTRIBUTES = Park_Boundary,"Name,Type,Park_Home_Page,Availability,UseType,OBJECTID,SHAPE__Area,SHAPE__Length",Park_Centroid,"Name,OBJECTID"
    ATTR_ACCUM_MODE = Only Use Result
    COMBINE_GEOM = Use Result
    FEATURETYPES = Park_Boundary Park_Centroid
    FORMAT = ARCGISONLINEFEATURES
    INTERACT = NONE
    ORDER_RESULTS = No
    OUTPUT_FEATURES_DISPLAY = Schema and Data Features
    Park_Centroid -> StringReplacer_5
Note: remove SP
StringReplacer_5
    CASE = NO
    FIND_TEXT = SP
    NO_MATCH = _FME_NO_OP_
    REGEXP = NO
    SRC_ATTRS = Name
    -> StringReplacer_6
Note: remove SNA
StringReplacer_6
    CASE = NO
    FIND_TEXT = SNA
    NO_MATCH = _FME_NO_OP_
    REGEXP = NO
    SRC_ATTRS = Name
    -> FeatureMerger [SUPPLIER]
Note: Merge on name to get the Geom
FeatureMerger
    ATTR_ACCUM_MODE = Merge Supplier
    ATTR_CONFLICT_RES = Use Requestor
    IGNORE_NULLS = No
    JOIN_KEYS = @Value(Campground) @Value(Name) AUTO
    MERGE_TYPE = Attributes and Geometry
    PROCESS_DUPS = NO
    REJECT_NULL_MISSING_KEYS = No
    SUPPLIERS_FIRST = No
    MERGED -> Reprojector
Note: Set field to lower case
BulkAttributeRenamer
    ATTRCHOICE = All Attributes
    CASE_CHANGE_TYPE = lower
    MODE_CHOICE = RENAME
    PATTERN_ACTION_DISP = CASECHANGE
    -> AttributeManager_4
AttributeManager_4
    ATTR_TABLE:
      REMOVE text_line_data (buffer)
      REMOVE fme_geometry{0} (fme_no_geom)
      REMOVE _dateslist{} (varchar(200))
      REMOVE fme_geometry{} (varchar(200))
      RENAME_SET_VALUE reservation number > reservation_number (varchar(200))
      REMOVE status (varchar(200))
      RENAME_SET_VALUE camp site > camp_site (varchar(200))
      RENAME_SET_VALUE reservation details > reservation_details (varchar(200))
      RENAME_SET_VALUE total fee > total_fee (varchar(200))
      REMOVE name (varchar(2048))
      REMOVE objectid (int32)
      RENAME_SET_VALUE longitude > Longitude (real64)
      RENAME_SET_VALUE latitude > Latitude (real64)
    -> ChangeDetector [REVISED]
ChangeDetector
    BLANK_AND_MISSING_DIFFER = No
    CHECK_TYPES_AND_ENCODINGS = No
    MATCHATTRS = att_data camp_site campground days fromdate Latitude levelness Longitude phone privacy reservation_details shade tmobile_data todate total_fee water OBJECTID
    MATCH_STRATEGY = Match Selected Attributes
    PREEMPTIVE_ATTRS = reservation_number
    UNCHANGED_OUTPUT = Output Original
    UPSERT_MODE = No
    UPDATED -> FeatureMerger_2 [REQUESTOR]
    INSERTED -> FeatureWriter [Camp_Sites]
Note: merge to get the ObjectID
FeatureMerger_2
    ATTR_ACCUM_MODE = Merge Supplier
    ATTR_CONFLICT_RES = Use Requestor
    IGNORE_NULLS = No
    JOIN_KEYS = @Value(reservation_number) @Value(reservation_number) AUTO
    MERGE_TYPE = Attributes Only
    PROCESS_DUPS = NO
    REJECT_NULL_MISSING_KEYS = No
    SUPPLIERS_FIRST = No
    MERGED -> FeatureWriter [Camp_Sites]
Note: write to AGO
FeatureWriter [off]
    ARCGISONLINEFEATURES_ASYNC_WRITE = NO
    ARCGISONLINEFEATURES_DESTINATION_DATASETTYPE_VALIDATION = Yes
    ARCGISONLINEFEATURES_FEATURESERVICE = camping_history
    ARCGISONLINEFEATURES_FEATURES_PER_REQUEST = 1000
    ARCGISONLINEFEATURES_FEATURE_SERVICE_HANDLING = USE_EXISTING
    ARCGISONLINEFEATURES_FEATURE_SERVICE_SELECTION_SOURCE = User
    ARCGISONLINEFEATURES_FOLDER_NAME = Camping
    ARCGISONLINEFEATURES_NC = Mike Does GIS
    ARCGISONLINEFEATURES_TARGET_WKID = 102100
    ARCGISONLINEFEATURES_USE_GLOBAL_ID = No
    DATASET_ATTR = _dataset
    FEATURE_TYPE_LIST_ATTR = _feature_types
    FORMAT = ARCGISONLINEFEATURES
    TOTAL_FEATURES_WRITTEN_ATTR = _total_features_written

Bookmark: Prepare the camoing history data
Note: Read camping log
FeatureReader
    ATTRIBUTES = text_line,"text_line_data,fme_geometry{0}"
    ATTR_ACCUM_MODE = Only Use Result
    COMBINE_GEOM = Use Result
    DATASET = $(FME_MF_DIR_ENCODED)TPWD Camping History Extract.txt
    FEATURETYPES = text_line
    FORMAT = TEXTLINE
    OUTPUT_FEATURES_DISPLAY = Schema and Data Features
    TEXTLINE_CREATE_FEATURE_TABLES_FROM_DATA = Yes
    TEXTLINE_ENCODING = windows-1252
    TEXTLINE_READ_BOTTOM_UP = No
    TEXTLINE_READ_WHOLE_FILE_AT_ONCE = NO
    TEXTLINE_SKIP_FOOTER = 0
    TEXTLINE_SKIP_LINES = 0
    text_line -> Tester
Note: Remove some lines we don't need
Tester
    BOOL_OP = OR
    TEST_CLAUSE = TEST @Value(text_line_data) = See Detail
    TEST_MODE = TEST
    FAILED -> AttributeManager
Note: Set the reservation number
AttributeManager
    ATTR_TABLE:
      SET_TO Reservation Number = FME_CONDITIONAL:DEFAULT_VALUE'_FME_NO_OP_'BOOL_OP;OR;COMPOSITE_TEST;1;CASE_INSENSITIVE_TEST @Value(text_line_data) CONTAINS TX'@Value(text_line_data)'FME_NUM_CONDITIONS2___
      SET_TO Status = FME_CONDITIONAL:DEFAULT_VALUE'_FME_NO_OP_'BOOL_OP;OR;COMPOSITE_TEST;1;CASE_INSENSITIVE_TEST @Value(text_line_data) CONTAINS TX'@Value(feature[+1].text_line_data)'FME_NUM_CONDITIONS2___
      SET_TO Campground = FME_CONDITIONAL:DEFAULT_VALUE'_FME_NO_OP_'BOOL_OP;OR;COMPOSITE_TEST;1;CASE_INSENSITIVE_TEST @Value(text_line_data) CONTAINS TX'@Value(feature[+2].text_line_data)'FME_NUM_CONDITIONS2___
      SET_TO Camp Site = FME_CONDITIONAL:DEFAULT_VALUE'_FME_NO_OP_'BOOL_OP;OR;COMPOSITE_TEST;1;CASE_INSENSITIVE_TEST @Value(text_line_data) CONTAINS TX'@Value(feature[+3].text_line_data)'FME_NUM_CONDITIONS2___
      SET_TO Reservation Details = FME_CONDITIONAL:DEFAULT_VALUE'_FME_NO_OP_'BOOL_OP;OR;COMPOSITE_TEST;1;CASE_INSENSITIVE_TEST @Value(text_line_data) CONTAINS TX'@Value(feature[+4].text_line_data)'FME_NUM_CONDITIONS2___
      SET_TO Total Fee = FME_CONDITIONAL:DEFAULT_VALUE'_FME_NO_OP_'BOOL_OP;OR;COMPOSITE_TEST;1;CASE_INSENSITIVE_TEST @Value(text_line_data) CONTAINS TX'@Value(feature[+5].text_line_data)'FME_NUM_CONDITIONS2___
    NUM_PRIOR_FEATURES = 0
    NUM_SUBSEQUENT_FEATURES = 6
    USER_EXPOSED_ATTRIBUTES = fme_geometry{}
    -> Tester_2
Note: remove empty rows
Tester_2
    BOOL_OP = OR
    TEST_CLAUSE = TEST Reservation Number ATTRIBUTE_HAS_A_VALUE ""
    TEST_MODE = TEST
    PASSED -> TestFilter
TestFilter
    DEFAULT_VALUE = Overnight
    PASSED_TEST_GROUP_OUTPUT = FIRST
    TEST_LIST:
      "BOOL_OP,OR,COMPOSITE_TEST,""""""1"""""",TEST_CLAUSE,TEST @Value(Status) = Cancelled",Cancelled,"BOOL_OP,OR,COMPOSITE_TEST,""""""1"""""",TEST_CLAUSE,CASE_INSENSITIVE_TEST @Value(Campground) CONTAINS Day Passes",Day Pass,"BOOL_OP,OR,COMPOSITE_TEST,""""""1 OR 2"""""",TEST_CLAUSE,CASE_INSENSITIVE_TEST @Value(Camp Site) CONTAINS CABIN
      CASE_INSENSITIVE_TEST @Value(Camp Site) CONTAINS BUNK",Cabin
    Cancelled -> StringReplacer
    Day Pass -> StringReplacer
    Cabin -> StringReplacer
    Overnight -> StringReplacer
Note: Calculate number of days for the reservation
DateTimeCalculator
    MODE = DATETIMECALC_3_CALCULATE_INTERVAL
    OPERATION_PARAMETERS = START_DATETIME]@Value(fromdate)]END_DATETIME]@Value(todate)]RESULT_TYPE]DAYS]RESULT_INTERVAL]days]FME_CONTROLLER_QUERY_FILE]transformers/dependencies/datetimecalculator/DATETIMECALC_3_CALCULATE_INTERVAL.fme]FME_CONTROLLER_CHOICE]DATETIMECALC_3_CALCULATE_INTERVAL
    -> StringReplacer_4
Note: remove state park
StringReplacer_4
    CASE = NO
    FIND_TEXT = state park
    NO_MATCH = _FME_NO_OP_
    REGEXP = NO
    SRC_ATTRS = Campground
    -> StringReplacer_7
Note: replacedouble spaces
StringReplacer_7
    CASE = NO
    FIND_TEXT = "  "
    NO_MATCH = _FME_NO_OP_
    REGEXP = NO
    REPLACE_TEXT = "  - "
    SRC_ATTRS = Campground
    -> StringReplacer_8
Note: replace dollar sign
StringReplacer_8
    CASE = NO
    FIND_TEXT = $
    NO_MATCH = _FME_NO_OP_
    REGEXP = NO
    SRC_ATTRS = Total Fee
    -> AttributeManager_3
Note: cleanup the attributes
AttributeManager_3
    -> FeatureMerger [REQUESTOR]

Bookmark: Campground info
Note: Clean up campground text
StringReplacer
    CASE = NO
    FIND_TEXT = Site
    NO_MATCH = _FME_NO_OP_
    REGEXP = NO
    SRC_ATTRS = Campground
    -> AttributeTrimmer
Note: Remove Tab character
AttributeTrimmer
    SRC_ATTRS = Campground
    TRIM_CHARS = "\t"
    TRIM_TO_NONE = Yes
    TRIM_TYPE = Both
    -> StringReplacer_2

Bookmark: Camp site info
Note: Remove site text
StringReplacer_2
    CASE = NO
    FIND_TEXT = Site:
    NO_MATCH = _FME_NO_OP_
    REGEXP = NO
    SRC_ATTRS = Camp Site
    -> AttributeTrimmer_2
Note: remove space character
AttributeTrimmer_2
    SRC_ATTRS = "Camp Site"
    TRIM_CHARS = " "
    TRIM_TO_NONE = Yes
    TRIM_TYPE = Both
    -> StringReplacer_3

Bookmark: date time info
Note: remove extra text from date
StringReplacer_3
    CASE = NO
    FIND_TEXT = \(([^)]+)\)
    NO_MATCH = _FME_NO_OP_
    REGEXP = YES
    SRC_ATTRS = Reservation Details
    -> AttributeSplitter
Note: split the dates
AttributeSplitter
    ATTR_NAME = Reservation Details
    DELIMITER = " - "
    DROP_EMPTY_PARTS = No
    LIST_NAME = _dateslist
    TRIM_OPTION = Both
    -> AttributeManager_2
Note: set the from and to date to their own fields
AttributeManager_2
    ATTR_TABLE:
      SET_TO fromdate = @Value(_dateslist{0})
      SET_TO todate = @Value(_dateslist{1})
    -> DateTimeConverter
DateTimeConverter
    DATETIME_ATTR = todate fromdate
    IN_FORMAT = * %b %d %Y
    OUT_FORMAT = FME
    PASSTHROUGH = YES
    REPAIR_INPUT = YES
    -> DateTimeCalculator

Bookmark: Get the Coords
Note: reproject to wgs 84 so we can extract XY
Reprojector
    DEST = EPSG:4326
    INTERPOLATION_TYPE_NAME = Nearest Neighbor
    RASTER_CELL_SIZE = Preserve Cells
    RASTER_TOLERANCE = 0.0
    REPROJECTED -> CoordinateExtractor
Note: extract the XY to field
CoordinateExtractor
    IND = 0
    MODE = Specify Coordinate
    X_ATTR = Longitude
    Y_ATTR = Latitude
    -> Reprojector_2
Note: reproject back to Web Mercator so we can write to AGO
Reprojector_2
    DEST = EPSG:3857
    INTERPOLATION_TYPE_NAME = Nearest Neighbor
    RASTER_CELL_SIZE = Preserve Cells
    RASTER_TOLERANCE = 0.0
    REPROJECTED -> BulkAttributeRenamer
