FME workspace TPWD Data to AGO.fmw

Creator
    GEOMTYPE = Geometry Object
    NUM = 1
    CREATED -> FeatureReader_2 [INITIATOR]
    CREATED -> HTTPCaller_2
    CREATED -> FeatureReader_4 [INITIATOR]
Note: TPWD AGO
FeatureReader_4
    ARCGISFEATURES_ARCGISFEATURES_EXPOSE_FORMAT_ATTRS = fme_basename,String(50)
    ARCGISFEATURES_AUTH_TYPE = None
    ARCGISFEATURES_CREATE_FEATURE_TABLES_FROM_DATA = Yes
    ARCGISFEATURES_FEATURES_PER_REQUEST = 1000
    ARCGISFEATURES_FORMAT_GUID = YES
    ARCGISFEATURES_QUERY_FEATURE_TYPES_FOR_MERGE_FILTERS = Yes
    ARCGISFEATURES_RESOLVE_DOMAINS = No
    ARCGISFEATURES_USE_SEARCH_ENVELOPE = NO
    ARCGISFEATURES_VERIFY_HTTPS = Yes
    ATTRIBUTES = "Bridge Points","OBJECTID,LoCode,ParkName,Category,Name1,Type,LowWater,Material,WidthFT,LengthFT,AreaSQFT,ADA,RTname,Traverses,LoadLimits,Historic,PropNo,AssetID,UTMZone,UTMX,UTMY,DMSX,DMSY,DDX,DDY,DDMX,DDMY,SrcType,SrcName,SrcOrigin,SrcScale,SrcDate,DataOrigin,DataDate,EditDate,Editor,GlobalID,Creator,CreatedDate,LastEditor,LastEditDate,fme_basename","Buildings and Structures","OBJECTID,LoCode,ParkName,Category,BldgStruc,PropNo,Descriptor,NameProper,NameFunction,Lineage,ConstType,ConstDate,CalcSF,InteriorSF,BldgDIM,BldgADA,Location,SiteNumber,NatlRegiser,Historic,Comments,UTMZone,SrcType,SrcName,SrcOrigin,SrcScale,SrcDate,DataOrigin,DataDate,EditDate,Editor,GlobalID,Creator,CreatedDate,LastEditor,LastEditDate,fme_basename",Campgrounds,"OBJECTID,LoCode,ParkName,Campground,SiteNumber,SiteClass,SiteAccess,Historic,PropNo,Comments,UTMZone,UTMX,UTMY,DMSX,DMSY,DDX,DDY,DDMX,DDMY,SrcType,SrcName,SrcOrigin,SrcScale,SrcDate,DataOrigin,DataDate,EditDate,Editor,GlobalID,Creator,CreatedDate,LastEditor,LastEditDate,fme_basename","Day Use","OBJECTID,LoCode,ParkName,SiteName,AcresCalc,Comments,UTMZone,UTMX,UTMY,DMSX,DMSY,DDX,DDY,DDMX,DDMY,SrcType,SrcName,SrcOrigin,SrcScale,SrcDate,DataOrigin,DataDate,EditDate,Editor,GlobalID,Creator,CreatedDate,LastEditor,LastEditDate,fme_basename","Gate Points","OBJECTID,LoCode,ParkName,EntryType,AccessType,Category,Name,EmergencyUse,Gated,Locked,Vehicular,AdjOwner,Historic,PropNo,AssetID,Comments,UTMZone,UTMX,UTMY,DMSX,DMSY,DDX,DDY,DDMX,DDMY,SrcType,SrcName,SrcOrigin,SrcScale,SrcDate,DataOrigin,DataDate,EditDate,Editor,GlobalID,Creator,CreatedDate,LastEditor,LastEditDate,fme_basename","Park HQ Points","OBJECTID,LoCode,ParkName,Type,County,Phone,Street,City,Zip,Comments,URL,Directions,Availability,UseType,UTMZone,UTMX,UTMY,DMSX,DMSY,DDX,DDY,WebMerc84X,WebMerc84Y,SrcType,SrcName,SrcOrigin,SrcScale,SrcDate,DataOrigin,DataDate,EditDate,Editor,GlobalID,Status,Creator,CreatedDate,LastEditor,LastEditDate,fme_basename","Park Regions","OBJECTID,Region,Comments,SrcType,SrcName,SrcOrigin,SrcScale,SrcDate,DataOrigin,DataDate,EditDate,Editor,GlobalID,Creator,CreatedDate,LastEditor,LastEditDate,Shape_Length,Shape_Area,fme_basename","Road Lines","OBJECTID,LoCode,ParkName,Desgntn,Name1,Name2,Paved,Material,Access,TPWDclass,CertMile,CertDate,WidthFT,Miles,Historic,PropNo,AssetID,Comments,UTMZone,SrcType,SrcName,SrcOrigin,SrcScale,SrcDate,DataOrigin,DataDate,EditDate,Editor,GlobalID,Creator,CreatedDate,LastEditor,LastEditDate,Shape_Length,fme_basename","TPWD Properties","OBJECTID,LoCode,LoName,BndryType,TPWDivision,County1,County2,County3,County4,CalcAcres,DeedAcres,Comments,UTMZone,SrcType,SrcName,SrcOrigin,SrcScale,SrcDate,DataOrigin,DataDate,EditDate,Editor,Creator,CreatedDate,LastEditor,LastEditDate,GlobalID_1,OrgCode,Shape_Length,Shape_Area,fme_basename","Trail Lines","OBJECTID,LoCode,ParkName,SegNum,Official,Name1,Name2,Name3,Name4,Name5,Name6,PublicTrail,ADA,TrailRating,TrailClosure,TrailSurface,Tracktype,TrailUse,LengthFT,LengthMI,TotalRiseFT,PctGrade,Historic,AssetID,Comments,UTMZone,SrcType,SrcName,SrcOrigin,SrcScale,SrcDate,DataOrigin,DataDate,EditDate,Editor,GlobalID,Creator,CreatedDate,LastEditor,LastEditDate,Shape_Length,fme_basename","Utility Lines","OBJECTID,UtiltiyLnID,LoCode,ParkName,Service,Descriptor,Type,Placement,Historic,FireHazard,Comments,UTMZone,SrcType,SrcName,SrcOrigin,SrcScale,SrcDate,DataOrigin,DataDate,EditDate,Editor,GlobalID,Creator,CreatedDate,LastEditor,LastEditDate,Shape_Length,fme_basename","Utility Points","OBJECTID,UtiltiyPtID,LoCode,ParkName,Service,Descriptor,Placement,Historic,FireHazard,Comments,UTMZone,UTMX,UTMY,DMSX,DMSY,DDX,DDY,DDMX,DDMY,SrcType,SrcName,SrcOrigin,SrcScale,SrcDate,DataOrigin,DataDate,EditDate,Editor,GlobalID,EffectUsge,Key_EU,Creator,CreatedDate,LastEditor,LastEditDate,fme_basename","Water Flow Lines","OBJECTID,LoCode,ParkName,FID_NHDFlowlines24k,COMID,FDATE,RESOLUTION,GNIS_ID,GNIS_NAME,LENGTHKM,REACHCODE,FLOWDIR,WBAREACOMID,FTYPE,FCODE,Comments,UTMZone,SrcType,SrcName,SrcOrigin,SrcScale,SrcDate,DataOrigin,DataDate,EditDate,Editor,GlobalID,Creator,CreatedDate,LastEditor,LastEditDate,Shape_Length,fme_basename"
    ATTR_ACCUM_MODE = Only Use Result
    COMBINE_GEOM = Use Result
    DATASET = https://tpwd.texas.gov/server/rest/services/Cultural/NRV_DEV_for_CRViewer_on_PRO/MapServer
    FEATURETYPES = Buildings and Structures Campgrounds Day Use Road Lines TPWD Properties Trail Lines Utility Points
    FORMAT = ARCGISFEATURES
    GEOMETRY_TYPES = "Bridge Points",""",fme_point""","Buildings and Structures",""",fme_point""",Campgrounds,""",fme_point""","Day Use",""",fme_point""","Gate Points",""",fme_point""","Park HQ Points",""",fme_point""","Park Regions",""",fme_area""","Road Lines",""",fme_line""","TPWD Properties",""",fme_area""","Trail Lines",""",fme_line""","Utility Lines",""",fme_line""","Utility Points",""",fme_point""","Water Flow Lines",""",fme_line"""
    INTERACT = NONE
    ORDER_RESULTS = No
    OUTPUT_ADD_SCHEMA_ATTRIBUTES = NO
    OUTPUT_FEATURES_DISPLAY = Schema and Data Features
    Campgrounds -> AttributeManager
AttributeManager
Note: Write to AGO
FeatureWriter [off]
    ARCGISONLINEFEATURES_DESTINATION_DATASETTYPE_VALIDATION = Yes
    ARCGISONLINEFEATURES_FEATURESERVICE = camping
    ARCGISONLINEFEATURES_FEATURES_PER_REQUEST = 1000
    ARCGISONLINEFEATURES_NC = Mike Does GIS
    ARCGISONLINEFEATURES_TARGET_WKID = 102100
    ARCGISONLINEFEATURES_USE_GLOBAL_ID = No
    DATASET_ATTR = _dataset
    FEATURE_TYPE_LIST_ATTR = _feature_type
    FORMAT = ARCGISONLINEFEATURES
    TOTAL_FEATURES_WRITTEN_ATTR = _total_features_written

Bookmark: Extract data from map page
HTTPCaller_2 [off]
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE_LOOKUP = NO
    STATUS_CODE_ATTR = _http_status_code
    TARGET_ATTR = _response_body
    TARGET_ATTR_ENCODING = auto-detect
    TARGET_URL = https://tpwd.texas.gov/state-parks/parks-map
    TRANSFER_TIMEOUT_LENGTH = 90
    USE_COOKIES = No
    VERIFY_SSL_CERTIFICATES = Yes
    SAVE_FILE = Attribute
    -> HTMLExtractor [off]
Note: Extract the Javascript / into a list
HTMLExtractor [off]
    HTML_FIELD = @Value(_response_body)
    HTML_SPECIFICATION = Content
    RESULT_TYPE_NAME = LIST_ATTR
    SEARCH_TABLE = jsonResults script Value
    Results -> ListExploder [off]
ListExploder [off]
    ATTR_ACCUM_MODE = Merge List Attributes
    ATTR_CONFLICT_RES_LOOKUP = INCOMING_IF_CONFLICT
    INDEX_ATTR = _element_index
    LIST_ATTR = jsonResults{}
    ATTR_CONFLICT_RES = Use List Attribute Values
    ELEMENTS -> Tester [off]
Tester [off]
    BOOL_OP = OR
    TEST_CLAUSE = CASE_INSENSITIVE_TEST @Value(jsonResults) CONTAINS var jsonResults=
    TEST_MODE = TEST
    PASSED -> StringReplacer_4 [off]
StringReplacer_4 [off]
    CASE = NO
    FIND_TEXT = var jsonResults=
    NO_MATCH = _FME_NO_OP_
    REGEXP = NO
    SRC_ATTRS = jsonResults
    -> JSONFragmenter [off]
JSONFragmenter [off]
    EXPLODE_FORMAT = JSON
    EXTRACT_ATTR = Yes
    JSON_ATTR = jsonResults
    JSON_QUERY = json[*]
    NEW_ATTRIBUTES = name url image idname notices status city longitude latitude address amenities zip
    READ_FROM_FILE = NO
    RECURSIVE_LOOKUP = NO
    REJECT_EMPTY_LISTS = YES
    RECURSIVE = No
    FRAGMENTS -> ListDuplicateRemover [off]
ListDuplicateRemover [off]
    SRC_LIST = location.amenities{}
    -> ListConcatenator [off]
ListConcatenator [off]
    DROP_EMPTY_PARTS = No
    LIST_ATTR = location.amenities{}
    SEP = ", "
    VAL_ATTR = Amenities
    -> ListSorter [off]
ListSorter [off]
    ORDER = Ascending
    SRC_LIST = location.amenities{}
    TYPE = Alphabetic

Bookmark: Mational Park Boundaries
Note: National Parks
FeatureReader_2 [off]
    ARCGISFEATURES_AUTH_TYPE = None
    ARCGISFEATURES_FEATURES_PER_REQUEST = 1000
    ARCGISFEATURES_QUERY_FEATURE_TYPES_FOR_MERGE_FILTERS = Yes
    ARCGISFEATURES_USE_SEARCH_ENVELOPE = NO
    ATTRIBUTES = nps_boundary,"OBJECTID,UNIT_CODE,GIS_Notes,UNIT_NAME,DATE_EDIT,STATE,REGION,GNIS_ID,UNIT_TYPE,CREATED_BY,METADATA,PARKNAME,CreationDate,Creator,EditDate,Editor,Shape__Area,Shape__Length,GlobalID",nps_boundary_centroids,"OBJECTID,UNIT_CODE,UNIT_NAME,DATE_EDIT,STATE,REGION,GNIS_ID,UNIT_TYPE,CREATED_BY,PARKNAME,CreationDate,Creator,EditDate,Editor,GlobalID",nps_tracts,"OBJECTID,TRACT_ID,ALPHA,NPS_DATEU,KEEP,KEY_,ALPHA_TRACT,STATENAME,AREA_TRACT,DEED,ESTATE,STATUS,REGION,ATTRIBUTE,Interest,CreationDate,Creator,EditDate,Editor,Shape__Area,Shape__Length,GlobalID"
    ATTR_ACCUM_MODE = Only Use Result
    COMBINE_GEOM = Use Result
    DATASET = https://services1.arcgis.com/fBc8EJBxQRMcHlei/arcgis/rest/services/NPS_Land_Resources_Division_Boundary_and_Tract_Data_Service/FeatureServer/
    FEATURETYPES = nps_boundary nps_boundary_centroids
    FORMAT = ARCGISFEATURES
    INTERACT = <No Spatial Filter>
    OUTPUT_FEATURES_DISPLAY = Schema and Data Features
    nps_boundary -> AttributeManager_2 [off]
    nps_boundary -> CenterPointReplacer_2 [off]
AttributeManager_2 [off]
    ATTR_TABLE:
      REMOVE OBJECTID
      RENAME_SET_VALUE UNIT_CODE > Park_Home_Page = https://www.nps.gov/@Value(Park_Home_Page)/
      REMOVE GIS_Notes
      REMOVE UNIT_NAME
      REMOVE DATE_EDIT
      REMOVE STATE
      REMOVE REGION
      REMOVE GNIS_ID
      RENAME_SET_VALUE UNIT_TYPE > Type
      REMOVE CREATED_BY
      REMOVE METADATA
      RENAME_SET_VALUE PARKNAME > Name
      REMOVE CreationDate
      REMOVE Creator
      REMOVE EditDate
      REMOVE Editor
      REMOVE Shape__Area
      REMOVE Shape__Length
      REMOVE GlobalID
    -> FeatureWriter [Output] [off]
CenterPointReplacer_2 [off]
    POINTTYPE = CENTER
    POINT -> AttributeManager_3 [off]
AttributeManager_3 [off]
    ATTR_TABLE:
      REMOVE OBJECTID
      REMOVE UNIT_CODE
      REMOVE GIS_Notes
      REMOVE UNIT_NAME
      REMOVE DATE_EDIT
      REMOVE STATE
      REMOVE REGION
      REMOVE GNIS_ID
      REMOVE UNIT_TYPE
      REMOVE CREATED_BY
      REMOVE METADATA
      RENAME_SET_VALUE PARKNAME > Name
      REMOVE CreationDate
      REMOVE Creator
      REMOVE EditDate
      REMOVE Editor
      REMOVE Shape__Area
      REMOVE Shape__Length
      REMOVE GlobalID
    -> FeatureWriter [Point] [off]
